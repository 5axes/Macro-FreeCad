#!/usr/bin/env python
# -*- coding: utf-8 -*-
#***************************************************************************
#*                                                                         *
#*   Copyright (c) 2023 5@xes                           *
#*                                                                         *
#*   This program is free software; you can redistribute it and/or modify  *
#*   it under the terms of the GNU Lesser General Public License (LGPL)    *
#*   as published by the Free Software Foundation; either version 2 of     *
#*   the License, or (at your option) any later version.                   *
#*   for detail see the LICENCE text file.                                 *
#*                                                                         *
#*   This program is distributed in the hope that it will be useful,       *
#*   but WITHOUT ANY WARRANTY; without even the implied warranty of        *
#*   MERCHANTABILITY or FITNESS FOR A PARTICULAR PURPOSE.  See the         *
#*   GNU Library General Public License for more details.                  *
#*                                                                         *
#*   You should have received a copy of the GNU Library General Public     *
#*   License along with this program; if not, write to the Free Software   *
#*   Foundation, Inc., 59 Temple Place, Suite 330, Boston, MA  02111-1307  *
#*   USA                                                                   *
#*                                                                         *
#***************************************************************************
"""
FreeCAD Surface Symbols
INSTALLATION
This script is made to be used as a FreeCAD macro, and to be placed
inside your macros  (default is $HOME/.FreeCAD/Macro on mac/linux,
C:/Users/youruser/Application Data/FreeCAD/Macro on windows).
After it is installed on the above location, it will be available
in the macros menu.
USAGE
Edit an Edge symbol (ISO 13715) and add it to a TechDraw drawing
"""
from __future__ import division

__Name__ = 'FreeCAD Edge Symbols'
__Author__ = '5@xes'
__Version__ = '2.0'
__Date__ = '2023-04-19'
__License__ = 'LGPL-2.0-or-later'
__Web__ = 'http://www.freecadweb.org'
__Wiki__ = ''
__Icon__ = ''
__Help__ = 'Launch, Edit the Edge symbol and add it to a TechDraw drawing'
__Status__ = ''
__Requires__ = 'FreeCAD v0.20+'
__Communication__ = ''
__Files__ = 'TaskEdgeSymbols.ui EdgeSymbols.FCMacro'

import FreeCAD,FreeCADGui,Part
import math
from PySide import QtCore # neu
from PySide import QtGui
from PySide import QtSvg
from functools import partial
from io import StringIO

class SvgFile():
    '''class to create svg files'''

    def __init__(self):
        self.file = ''
        self.svgHead(100,100)
        self.svgFont = "osifont"
        param_draft = FreeCAD.ParamGet("User parameter:BaseApp/Preferences/Mod/TechDraw/Labels")
        th = param_draft.GetFloat("LabelSize", 18)
        th *= 1.3333 # temporary solution to get the Right Size but it's not normal
        # Millimeter to Pixel (X) Conversion Table
        self.px=int(th * 3.7795275591)
        
    def svgHead(self,width,high):
        '''create head of a svg file'''
        version = '<?xml version="1.0"?>\n'
        size =  '<svg width="'+str(width)+'" height="'+str(high)+'">\n'
        self.file = self.file + version + size

    def svgLine(self,x1,y1,x2,y2,width):
        '''create one line in the svg file'''
        startPnt = ' M'+str(x1)+','+str(y1)
        endPnt = ' L'+str(x2)+','+str(y2)
        line =  '<path stroke="#000" stroke-width="'+str(width)+'" d="'+startPnt+endPnt+'" />\n'
        self.file = self.file + line

    def svgArrow(self,x1,y1,x2,y2,width,angle):
        '''create one line in the svg file'''
        startPnt = ' M'+str(x1)+','+str(y1)
        endPnt = ' L'+str(x2)+','+str(y2)
        line =  '<g><path d="'+startPnt+endPnt+'" stroke="#000000" stroke-width="'+str(width)+'" /></g>\n'
        line +=  '<g transform="translate('+str(x2)+','+str(y2)+')" > <path transform="rotate('+str(angle)+')" d="M 0.0,0.0 12.0,3.0 12.0,-3.0 0.0,0.0 Z" fill="#000000" stroke="#000000" /></g>\n'
        self.file = self.file + line
        
    def svgCircle(self,xCenter,yCenter,radius,width):
        '''create one circle in the svg file'''
        circle = '<circle cx="'+str(xCenter)+'" cy="'+str(yCenter)+'" r="'+str(radius)+'" fill="none" stroke="#000" stroke-width="'+str(width)+'"/>'
        self.file = self.file + circle

    def svgText(self,xText,yText,text):
        '''create one text in the svg file'''               
        if len(self.svgFont) :
            line = '<text x="'+str(xText)+'" y="'+str(yText)+'" style="font-size:'+str(self.px)+'px;font-family:'+self.svgFont+'">'+text+'</text>\n'
        else :
            line = '<text x="'+str(xText)+'" y="'+str(yText)+'" style="font-size:'+str(self.px)+'px">'+text+'</text>\n'
        self.file = self.file + line

    def svgFinish(self):
        '''finish svg file'''
        self.file = self.file +  '</svg>\n'

class edgeSymbols:
    '''class to create surface symbols'''

    def baseSymbol(allAround):
        '''return file with base symbol'''
        svgFile = SvgFile()
        
        svgFile.svgLine(50,60,100,60,2)
        svgFile.svgLine(50,12,50,62,2)

        ''' Line for Arrow '''
        svgFile.svgLine(40,65,100,65,1)
        svgFile.svgArrow(40,65,10,90,1,-45)

        ''' Circle All Around '''
        if allAround == True:
            svgFile.svgCircle(40,65,6,1)
  
        svgFile.svgFinish()
        return svgFile.file

    def completeSymbol(angle,allAround, font):
        '''create the complete symbol shown in the drawing'''
        svgFile = SvgFile()
        svgFile.svgFont = font
        moveLeft = 0
        
        if allAround == True:
            svgFile.svgCircle(40,65,6,1) # all around
            moveLeft = 5
 
        additionText = panel.leAddition.text()
        additionTextLen = additionText.__len__()
        if additionTextLen :
            svgFile.svgText(50+moveLeft,60,panel.leAddition.text())
            moveLeft += additionTextLen*15
            
        svgFile.svgLine(50+moveLeft,60,100+moveLeft,60,2)
        svgFile.svgLine(50+moveLeft,12,50+moveLeft,61,2)
       
        ''' Line for arrow '''
        svgFile.svgLine(40,65,100+moveLeft,65,1)
        px = 50*math.cos(math.radians(angle-45))
        py = 50*math.sin(math.radians(angle-45))
        print("X {}  Y {}".format(px,py))
        svgFile.svgArrow(40,65,40-px,65-py,1,float(angle-45))
 
        undercutHightText = panel.undercutHight.text()
        undercutHightTextLen = undercutHightText.__len__()
        passingHightText = panel.passingHight.text()
        passingHightTextLen = passingHightText.__len__()
        if undercutHightTextLen :
            svgFile.svgText(30+moveLeft,-30,undercutHightText)  
        if passingHightTextLen :        
            svgFile.svgText(30+moveLeft,0,passingHightText)          
            
        edgePlusText = panel.edgePlus.text()
        edgePlusTextLen = edgePlusText.__len__()
        edgeMinusText = panel.edgeMinus.text()
        edgeMinusTextLen = edgeMinusText.__len__()
        if edgePlusTextLen :
            svgFile.svgText(60+moveLeft,20,edgePlusText)
        if edgeMinusTextLen :   
            svgFile.svgText(60+moveLeft,50,edgeMinusText)

        undercutLowText = panel.undercutLow.text()
        undercutLowTextLen = undercutLowText.__len__()
        passingLowText = panel.passingLow.text()
        passingLowTextLen = passingLowText.__len__()
        if undercutLowTextLen :
            svgFile.svgText(105+moveLeft,40,undercutHightText)
        if passingLowTextLen :
            svgFile.svgText(105+moveLeft,70,passingLowText)        
        

        
        svgFile.svgFinish()
        return svgFile.file

class DefinePanel:
    '''Define the combo-view panel'''
    def __init__(self):
        self.form = FreeCADGui.PySideUic.loadUi(path_to_ui)
        self.pbTabs = []
        self.aRound = False
        self.tab = 0 
        param_draft = FreeCAD.ParamGet("User parameter:BaseApp/Preferences/Mod/TechDraw/Labels")
        ft = param_draft.GetString("LabelFont", "osifont")
        self.symbolFont = ft
        # self.form.leFont.setText(ft) 
        font_db = QtGui.QFontDatabase()
        iind = 0
        prof = 0 
            
        self.form.rbAround.clicked.connect(self.on_ModeChanged)
        self.form.plusMoins.clicked.connect(self.on_plusMoins)
        
        self.createSceneItems()
        for font in font_db.families():
            if font == ft :
                prof = iind
            iind +=1
            self.form.leFont.addItem(font)
        self.form.leFont.setCurrentIndex(prof)
        
    def textureFromSvgString(self,svgString):
        ''' Render a svg-string to a pixmap'''
        byteArray = bytearray(svgString,'utf-8') # create byte array from string
        xmlStream = QtCore.QXmlStreamReader(byteArray) # create xml stream from byte array
        pixmap = QtGui.QPixmap() # create an empty pixmap
        svgRender = QtSvg.QSvgRenderer() # create an empty rendering container
        if svgRender.load(xmlStream): # load the xml stream into the container
            size = svgRender.defaultSize() # get container default size
            image = QtGui.QImage(size.width(),size.height(),QtGui.QImage.Format_RGB32) # create an empty image, having width, height and colors
            image.fill(QtGui.QColor(240,240,240)) # fill the background gray
            painting = QtGui.QPainter(image) # create a painting, fill it with the image
            svgRender.render(painting) # fill the svg into the image
            painting.end() # finish the image
            pixmap = QtGui.QPixmap.fromImage(image)
        return pixmap
        
    def createSceneItems(self):
        '''Create scene and all items used in the scene'''
        self.scene = QtGui.QGraphicsScene() # create scene
        self.form.graphicsView.setScene(self.scene) # insert scene, graphicsView is an item of type QGraphicsView in TaskEdgeSymbols02.ui

        # LineEdit  showing edgePlus:
        self.edgePlus = QtGui.QLineEdit('')
        self.edgePlus.resize(40,20)
        self.scene.edgePlus = self.scene.addWidget(self.edgePlus)
        self.scene.edgePlus.setPos(0,-75)

        # LineEdit  showing edgeMinus:
        self.edgeMinus = QtGui.QLineEdit('-0,5')
        self.edgeMinus.resize(40,20)
        self.scene.edgeMinus = self.scene.addWidget(self.edgeMinus)
        self.scene.edgeMinus.setPos(0,-50)

        # LineEdit  showing undercutHight:
        self.undercutHight = QtGui.QLineEdit('')
        self.undercutHight.resize(40,20)
        self.scene.undercutHight = self.scene.addWidget(self.undercutHight)
        self.scene.undercutHight.setPos(-40,-135)
        
        # LineEdit  showing passingHight:
        self.passingHight = QtGui.QLineEdit('')
        self.passingHight.resize(40,20)
        self.scene.passingHight = self.scene.addWidget(self.passingHight)
        self.scene.passingHight.setPos(-40,-110)

        # LineEdit  showing undercutLow:
        self.undercutLow = QtGui.QLineEdit('')
        self.undercutLow.resize(40,20)
        self.scene.undercutLow = self.scene.addWidget(self.undercutLow)
        self.scene.undercutLow.setPos(50,-25)
        
        # LineEdit  showing passingLow:
        self.passingLow = QtGui.QLineEdit('')
        self.passingLow.resize(40,20)
        self.scene.passingLow = self.scene.addWidget(self.passingLow)
        self.scene.passingLow.setPos(50,0)
        
        # LineEdit  showing addition:
        self.leAddition = QtGui.QLineEdit('')
        self.leAddition.resize(40,20)
        self.scene.leAddition = self.scene.addWidget(self.leAddition)
        self.scene.leAddition.setPos(-90,-40)
        self.scene.leAddition.setZValue(1)

        # insert the symbol icon:
        self.on_ModeChanged()
    
    def on_tabChanged(self,id):
        self.tab = id
        print("on_tabChanged {}".format(id))
        
    def on_ModeChanged(self):
        '''slot: change the option all Around'''
        self.aRound = self.form.rbAround.isChecked()
        pixMap = self.textureFromSvgString(edgeSymbols.baseSymbol(self.aRound))
        pixmapItem = QtGui.QGraphicsPixmapItem(pixMap)
        pixmapItem.setPos(-60,-80)
        pixmapItem.setZValue(-2)
        sceneItem = self.scene.addItem(pixmapItem)

    def on_plusMoins(self):
        '''self.get_active_line_edit()'''        
        panel.edgeMinus.setText("±")   

  
    def get_active_line_edit(self):
        active_widget = None
        main_window = FreeCADGui.getMainWindow()
        if main_window:
            focus_widget = main_window.focusWidget()
            if isinstance(focus_widget, QtGui.QLineEdit):
                active_widget = focus_widget
        print("Clic de souris détecté {}".format(active_widget))
        return active_widget       
    
    def accept(self):
        '''slot: OK pressed'''
        doc = App.activeDocument()
        mySymbol = doc.addObject('TechDraw::DrawViewSymbol','EdgeSymbol')
        mySymbol.Symbol = edgeSymbols.completeSymbol(float(self.form.leAngle.text()),self.aRound,self.form.leFont.currentText())
        # print("{}".format(mySymbol.Symbol))
        page = doc.findObjects('TechDraw::DrawPage')
        nb=len(page)
        active_view = FreeCADGui.ActiveDocument.ActiveView
        gp=active_view.getPage()
        gp.addView(mySymbol)        # svg included as a string
        #page[nb].addView(mySymbol)
        FreeCADGui.Control.closeDialog()

path_to_ui = os.path.dirname(__file__) + "/TaskEdgeSymbols.ui"
panel=DefinePanel() 
FreeCADGui.Control.showDialog(panel)
