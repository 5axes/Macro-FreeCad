#Change Font in a TechDraw for Dimension, Ballon & Annotation
import FreeCADGui

_font = "Arial"

FreeCAD.ActiveDocument.RecomputesFrozen = True
# browse all objects in the view
for obj in FreeCADGui.ActiveDocument.Document.Objects:
	if obj.isDerivedFrom("TechDraw::DrawViewDimension") or obj.isDerivedFrom("TechDraw::DrawViewBalloon"):
		_name=obj.Name
		FreeCADGui.ActiveDocument.getObject(_name).Font = _font
	elif obj.isDerivedFrom("TechDraw::DrawViewAnnotation") :
		_name=obj.Name
		FreeCAD.ActiveDocument.getObject(_name).Font = _font		
FreeCAD.ActiveDocument.RecomputesFrozen = False
